module simplemonitor {
  yang-version 1.1;
  namespace "http://polycube.network/simplemonitor";
  prefix "simplemonitor";

  import polycube-base { prefix "polycube-base"; }
  import polycube-transparent-base { prefix "polycube-transparent-base"; }

  organization "Polycube open source project";
  description "YANG data model for the Polycube Simple Monitor service";

  polycube-base:service-description "Simple Monitor Service";
  polycube-base:service-version "1.0";
  polycube-base:service-name "simplemonitor";
  polycube-base:service-min-kernel-version "4.14.0";

  uses "polycube-transparent-base:transparent-base-yang-module";

  leaf ingress-action {
    type enumeration {
      enum DROP;
      enum PASS;
      enum SLOWPATH;
      enum TWO_WAY;
    }
    default PASS;
    description "Action performed on ingress packets";
  }

  leaf egress-action {
    type enumeration {
      enum DROP;
      enum PASS;
      enum SLOWPATH;
    }
    default PASS;
    description "Action performed on egress packets";
  }
}
